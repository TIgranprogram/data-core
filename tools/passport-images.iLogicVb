AddReference "System.Net.Http.dll"
AddReference "System.Net.Primitives.dll"
AddReference "System.Private.Uri.dll"
AddReference "System.Memory.dll"
AddReference "System.Text.Json.dll"

' Внешнее правило Inventor 2027. Запуск из сохранённой сборки или детали.
Sub Main()
    Dim app As Inventor.Application = ThisApplication
    Dim doc As Inventor.Document = app.ActiveDocument
    If doc Is Nothing Then Return
    Dim stage As String = "Открытие документа"

    Try
        Select Case doc.DocumentType
            Case Inventor.DocumentTypeEnum.kAssemblyDocumentObject,
                 Inventor.DocumentTypeEnum.kPartDocumentObject
                Prepare(app, doc, stage)
            Case Inventor.DocumentTypeEnum.kDrawingDocumentObject
                ' На чертеже (например, лист «Схема установки» с разрезом А-А) — убрать масштаб из подписей видов (2026-11-13)
                stage = "Подписи видов без масштаба"
                Dim changed As Integer = RemoveScaleFromLabels(CType(doc, Inventor.DrawingDocument))
                MessageBox.Show(If(changed > 0, "Масштаб убран из подписей видов: " & changed & "." & vbCrLf & "Для нового комплекта картинок запустите правило из модели.",
                    "Подписей с масштабом нет." & vbCrLf & "Для нового комплекта картинок запустите правило из модели."), "Картинки для паспорта")
            Case Else
                MessageBox.Show("Откройте сборку или деталь.")
        End Select
    Catch ex As Exception
        MessageBox.Show(stage & vbCrLf & ex.Message, "Картинки для паспорта")
    End Try
End Sub

' Подпись вида «А-А (0,08 : 1)» → «А-А»: из текста подписи убирается автоматический масштаб Inventor (тег DrawingViewScale)
' вместе со скобками — он дробный, не по ГОСТ. Масштаб ГОСТ, который пишет само правило («А-А (1:10)»), — обычный текст, остаётся.
' Возвращает число изменённых подписей.
Function RemoveScaleFromLabels(drawing As Inventor.DrawingDocument) As Integer
    Dim n As Integer = 0
    For Each sh As Inventor.Sheet In drawing.Sheets
        For Each v As Inventor.DrawingView In sh.DrawingViews
            If Not v.ShowLabel Then Continue For
            Dim t As String = v.Label.FormattedText
            Dim s As String = System.Text.RegularExpressions.Regex.Replace(t, "\s*\(\s*<DrawingViewScale[^>]*/>\s*\)", "")
            ' стиль ГОСТ: «…<Br/>МАСШТАБ <DrawingViewScale/>» — убираем перенос, слово и масштаб целиком
            s = System.Text.RegularExpressions.Regex.Replace(s, "(<Br/>)?\s*МАСШТАБ\s*<DrawingViewScale[^>]*/>", "", System.Text.RegularExpressions.RegexOptions.IgnoreCase)
            s = System.Text.RegularExpressions.Regex.Replace(s, "\s*<DrawingViewScale[^>]*/>", "")
            If s <> t Then
                v.Label.FormattedText = s
                n += 1
            End If
        Next
    Next
    If n > 0 Then drawing.Update()
    Return n
End Function

Sub Prepare(app As Inventor.Application, model As Inventor.Document, ByRef stage As String)
    If String.IsNullOrWhiteSpace(model.FullFileName) Then
        Throw New InvalidOperationException("Сначала сохраните модель.")
    End If
    Dim orientationChoice As DialogResult = MessageBox.Show(
        "Повернуть габаритные виды на 90° вокруг вертикали?" & vbCrLf &
        "Да — взять вид справа как фронт." & vbCrLf &
        "Нет — оставить стандартный вид спереди.",
        "Ориентация габаритного листа", MessageBoxButtons.YesNoCancel,
        MessageBoxIcon.Question, MessageBoxDefaultButton.Button2)
    If orientationChoice = DialogResult.Cancel Then Return
    Dim rotate As Boolean = orientationChoice = DialogResult.Yes

    stage = "Поиск метрического шаблона ГОСТ"
    Dim template As String = app.FileManager.GetTemplateFile(
        Inventor.DocumentTypeEnum.kDrawingDocumentObject,
        Inventor.SystemOfMeasureEnum.kMetricSystemOfMeasure,
        Inventor.DraftingStandardEnum.kGOST_DraftingStandard)
    If Not String.IsNullOrWhiteSpace(template) AndAlso
       Not String.Equals(System.IO.Path.GetFileNameWithoutExtension(template), "GOST", StringComparison.OrdinalIgnoreCase) Then
        template = System.IO.Path.Combine(System.IO.Path.GetDirectoryName(template),
            "GOST" & System.IO.Path.GetExtension(template))
    End If
    If Not System.IO.File.Exists(template) OrElse
       Not String.Equals(System.IO.Path.GetFileNameWithoutExtension(template), "GOST", StringComparison.OrdinalIgnoreCase) Then
        Dim publicDocuments As String = Global.System.Environment.GetFolderPath(
            Global.System.Environment.SpecialFolder.CommonDocuments)
        Dim installedTemplates As String = System.IO.Path.Combine(
            publicDocuments, "Autodesk", "Inventor 2027", "Templates")
        template = System.IO.Path.Combine(installedTemplates, "ru-RU", "Metric", "GOST.idw")
        If Not System.IO.File.Exists(template) Then
            template = System.IO.Path.Combine(installedTemplates, "GOST.idw")
        End If
        If Not System.IO.File.Exists(template) Then
            Throw New InvalidOperationException("Не найден шаблон GOST.idw в " & installedTemplates)
        End If
    End If
    ' Одна папка на модель: прежний комплект удаляется целиком, новый пишется на его место (пользователь 2026-11-13)
    Dim folder As String = System.IO.Path.Combine(
        System.IO.Path.GetDirectoryName(model.FullFileName),
        System.IO.Path.GetFileNameWithoutExtension(model.FullFileName) & " — картинки паспорта")
    If System.IO.Directory.Exists(folder) Then
        stage = "Удаление прежней папки: " & folder
        ' открытый прежний чертёж держит файл — закрыть без сохранения (это копия, её всё равно заменяем)
        Dim prefix As String = System.IO.Path.GetFullPath(folder).TrimEnd("\"c) & "\"
        For i As Integer = app.Documents.Count To 1 Step -1
            Dim d As Inventor.Document = app.Documents.Item(i)
            If Not String.IsNullOrEmpty(d.FullFileName) AndAlso
               d.FullFileName.StartsWith(prefix, StringComparison.OrdinalIgnoreCase) Then d.Close(True)
        Next
        System.IO.Directory.Delete(folder, True)
    End If
    stage = "Создание папки: " & folder
    System.IO.Directory.CreateDirectory(folder)

    stage = "Экспорт общего вида"
    model.Activate()
    Dim view As Inventor.View = app.ActiveView
    Dim original As Inventor.Camera = view.Camera
    Dim camera As Inventor.Camera = view.Camera
    Dim restoreVisibility As New Global.System.Collections.Generic.List(Of Action)
    Dim assembly As Inventor.AssemblyDocument = TryCast(model, Inventor.AssemblyDocument)
    Dim visibility As Inventor.ObjectVisibility
    If assembly Is Nothing Then
        visibility = CType(model, Inventor.PartDocument).ObjectVisibility
    Else
        visibility = assembly.ObjectVisibility
    End If
    Try
        model.SelectSet.Clear()
        HideForExport(visibility, restoreVisibility)
        view.Update()
        camera.ViewOrientationType = Inventor.ViewOrientationTypeEnum.kIsoTopRightViewOrientation
        camera.Perspective = False
        camera.Fit()
        camera.ApplyWithoutTransition()
        SavePng(app, camera, folder, "01_Общий вид.png", 1800)
    Finally
        For Each restore As Action In restoreVisibility
            restore()
        Next
        original.ApplyWithoutTransition()
    End Try

    stage = "Создание листа A4"
    Dim drawing As Inventor.DrawingDocument = CType(app.Documents.Add(
        Inventor.DocumentTypeEnum.kDrawingDocumentObject, template, True),
        Inventor.DrawingDocument)
    Dim sheet As Inventor.Sheet = drawing.Sheets.Item(1)
    ' Если Inventor оставит бумагу непрозрачной, она будет белой.
    drawing.SheetSettings.SheetColor = app.TransientObjects.CreateColor(255, 255, 255)
    If sheet.TitleBlock IsNot Nothing Then sheet.TitleBlock.Delete()
    If sheet.Border IsNot Nothing Then sheet.Border.Delete()
    ClearTemplateGraphics(sheet)
    sheet.Size = Inventor.DrawingSheetSizeEnum.kA4DrawingSheetSize

    stage = "Построение вида спереди"
    Dim tg As Inventor.TransientGeometry = app.TransientGeometry
    Dim viewOptions As Inventor.NameValueMap = app.TransientObjects.CreateNameValueMap()
    viewOptions.Add("Include3DAnnotations", False)
    If assembly IsNot Nothing Then
        Dim representation As Inventor.DesignViewRepresentation =
            assembly.ComponentDefinition.RepresentationsManager.ActiveDesignViewRepresentation
        If representation IsNot Nothing AndAlso
           representation.DesignViewType = Inventor.DesignViewTypeEnum.kPublicDesignViewType Then
            viewOptions.Add("DesignViewRepresentation", representation.Name)
            viewOptions.Add("DesignViewAssociative", False)
        End If
    End If
    Dim frontOrientation As Inventor.ViewOrientationTypeEnum =
        If(rotate, Inventor.ViewOrientationTypeEnum.kRightViewOrientation,
                   Inventor.ViewOrientationTypeEnum.kFrontViewOrientation)
    Dim front As Inventor.DrawingView = sheet.DrawingViews.AddBaseView(
        model, tg.CreatePoint2d(sheet.Width * 0.46, sheet.Height * 0.74), 1,
        frontOrientation,
        Inventor.DrawingViewStyleEnum.kHiddenLineRemovedDrawingViewStyle, AdditionalOptions:=viewOptions)
    stage = "Построение вида сверху"
    Dim top As Inventor.DrawingView = sheet.DrawingViews.AddBaseView(
        model, tg.CreatePoint2d(sheet.Width * 0.46, sheet.Height * 0.31), 1,
        Inventor.ViewOrientationTypeEnum.kTopViewOrientation,
        Inventor.DrawingViewStyleEnum.kHiddenLineRemovedDrawingViewStyle, AdditionalOptions:=viewOptions)
    front.IncludeSurfaceBodies = False
    top.IncludeSurfaceBodies = False
    If rotate Then top.Rotation = -Math.PI / 2
    drawing.Update()

    ' Общий масштаб оставляет место для выносных и размерных линий.
    Dim viewWidth As Double = Math.Max(front.Width, top.Width)
    Dim viewHeight As Double = Math.Max(front.Height, top.Height)
    If front.Width <= 0 OrElse front.Height <= 0 OrElse
       top.Width <= 0 OrElse top.Height <= 0 Then
        Throw New InvalidOperationException("Виды пустые. Проверьте видимость компонентов.")
    End If
    stage = "Масштабирование видов"
    ' Виды — одним блоком: спереди, под ним сверху. Блок как можно крупнее и по центру листа (2026-11-13).
    ' Запас: снизу под видом спереди — линия длины (gap), справа — линии высоты и ширины (dimRoom).
    Const gap As Double = 1.8
    Const dimRoom As Double = 2.2
    Dim blockHeight As Double = front.Height + top.Height
    front.Scale = front.Scale * Math.Min((sheet.Width * 0.9 - dimRoom) / viewWidth,
                                         (sheet.Height * 0.9 - gap) / blockHeight)
    top.Scale = front.Scale
    drawing.Update()
    Dim centerX As Double = (sheet.Width - dimRoom) / 2
    Dim blockTop As Double = (sheet.Height + front.Height + gap + top.Height) / 2
    front.Position = tg.CreatePoint2d(centerX, blockTop - front.Height / 2)
    top.Position = tg.CreatePoint2d(centerX, blockTop - front.Height - gap - top.Height / 2)
    drawing.Update()
    stage = "Построение габаритных линий"
    Dim dimensions As Double() = AddDimensions(sheet, front, top, tg)
    drawing.Update()

    ' «Схема установки» (2026-11-13, проверено тестом tools/passport-section-test.iLogicVb на 3211): лист книжный;
    ' сверху вид спереди с линией земли (плоскость XZ модели) и размером «Г» от земли до низа опоры у левой опоры;
    ' снизу разрез А-А по линии земли — взгляд сверху на опоры, с габаритами; подпись «А-А (1:N)» под размером.
    ' Масштабы видов — из ряда ГОСТ 2.302 (GostScale).
    stage = "Создание листа «Схема установки»"
    Dim installationSheet As Inventor.Sheet = drawing.Sheets.Add(
        Inventor.DrawingSheetSizeEnum.kA4DrawingSheetSize,
        Inventor.PageOrientationTypeEnum.kPortraitPageOrientation, "Схема установки")
    If installationSheet.TitleBlock IsNot Nothing Then installationSheet.TitleBlock.Delete()
    If installationSheet.Border IsNot Nothing Then installationSheet.Border.Delete()
    ClearTemplateGraphics(installationSheet)
    Dim sW As Double = installationSheet.Width, sH As Double = installationSheet.Height
    Dim installationView As Inventor.DrawingView = installationSheet.DrawingViews.AddBaseView(
        model, tg.CreatePoint2d(sW * 0.5, sH * 0.7), 1, frontOrientation,
        Inventor.DrawingViewStyleEnum.kHiddenLineRemovedDrawingViewStyle, AdditionalOptions:=viewOptions)
    installationView.IncludeSurfaceBodies = False
    drawing.Update()
    ' масштаб вида спереди — из ряда ГОСТ 2.302, самый крупный, что помещается
    installationView.Scale = GostScale(installationView.Scale * Math.Min(sW * 0.6 / installationView.Width, sH * 0.36 / installationView.Height))
    drawing.Update()
    installationView.Position = tg.CreatePoint2d(sW * 0.5, sH * 0.7)
    drawing.Update()
    Dim fLeft As Double = installationView.Left, fRight As Double = installationView.Left + installationView.Width
    Dim fTop As Double = installationView.Top, fBottom As Double = installationView.Top - installationView.Height

    stage = "Линия земли (плоскость XZ) и глубина Г"
    Dim groundY As Double = installationView.ModelToSheetSpace(tg.CreatePoint(0, 0, 0)).Y
    ' глубина заложения: от земли до низа изделия, мм (0 — не заглублено); пойдёт в паспорт «Глубина Г = … мм»
    Dim depthMm As Double = Math.Max(0, Math.Round((groundY - fBottom) / installationView.Scale * 10))

    stage = "Линия разреза по земле"
    Dim cutSketch As Inventor.DrawingSketch = installationView.Sketches.Add()
    cutSketch.Edit()
    Try
        cutSketch.SketchLines.AddByTwoPoints(cutSketch.SheetToSketchSpace(tg.CreatePoint2d(fLeft - 0.5, groundY)),
                                            cutSketch.SheetToSketchSpace(tg.CreatePoint2d(fRight + 0.5, groundY)))
    Finally
        cutSketch.ExitEdit()
    End Try

    stage = "Разрез А-А"
    ' направление взгляда задаёт место разреза при создании: ВЫШЕ линии — смотрит вниз, на землю
    Dim section As Inventor.SectionDrawingView = installationSheet.DrawingViews.AddSectionView(installationView, cutSketch,
        tg.CreatePoint2d(sW * 0.5, fTop + 4), Inventor.DrawingViewStyleEnum.kHiddenLineRemovedDrawingViewStyle,
        Scale:=installationView.Scale, ShowLabel:=True, Name:="А")
    drawing.Update()
    ' пока масштаб и X общие — края разреза = крайние опоры на виде спереди
    Dim postsLeft As Double = section.Left

    stage = "Линия земли, штриховка, размер Г"
    Dim gl As Double = fLeft - 0.8, gr As Double = fRight + 0.8
    Dim gDimX As Double = postsLeft - 0.9
    Dim groundSketch As Inventor.DrawingSketch = installationSheet.Sketches.Add()
    groundSketch.Edit()
    Try
        AddLine(groundSketch, tg, gl, groundY, gr, groundY)
        Dim hx As Double = gl
        While hx < gr - 0.3
            AddLine(groundSketch, tg, hx, groundY, hx + 0.3, groundY - 0.3)
            hx += 0.5
        End While
        If depthMm > 0 Then
            AddLine(groundSketch, tg, postsLeft, fBottom, gDimX - 0.2, fBottom)
            AddArrowLine(groundSketch, tg, gDimX, fBottom, gDimX, groundY)
        End If
    Finally
        groundSketch.ExitEdit()
    End Try
    Dim cutNotes As Inventor.GeneralNotes = installationSheet.DrawingNotes.GeneralNotes
    If depthMm > 0 Then SchemeNote(cutNotes, tg, gDimX - 0.75, (fBottom + groundY) / 2 + 0.3, "Г", 0.5)

    stage = "Разрез под видом спереди, масштаб ГОСТ"
    ' масштаб разреза — из ряда ГОСТ 2.302: помещается в 40 % ширины и 18 % высоты листа, но не крупнее 1:10
    ' (столб Ø136 — 1:10; широкое основание — мельче). Масштаб пишется в подписи: «А-А (1:10)»
    section.ScaleFromBase = False
    section.Scale = GostScale(Math.Min(0.1, section.Scale * Math.Min(sW * 0.4 / section.Width, sH * 0.18 / section.Height)))
    drawing.Update()
    section.Position = tg.CreatePoint2d(sW * 0.5, Math.Max(fBottom - 2.5 - section.Height / 2, section.Height / 2 + 3))
    drawing.Update()
    section.Label.FormattedText = "<DrawingViewName/>-<DrawingViewName/> (" & ScaleText(section.Scale) & ")"

    stage = "Габариты по разрезу"
    Dim secLeft As Double = section.Left, secRight As Double = section.Left + section.Width
    Dim secTop As Double = section.Top, secBottom As Double = section.Top - section.Height
    Dim dimY As Double = secBottom - 0.9, dimX As Double = secRight + 0.9
    Dim cutDims As Inventor.DrawingSketch = installationSheet.Sketches.Add()
    cutDims.Edit()
    Try
        AddLine(cutDims, tg, secLeft, secBottom, secLeft, dimY - 0.2)
        AddLine(cutDims, tg, secRight, secBottom, secRight, dimY - 0.2)
        AddArrowLine(cutDims, tg, secLeft, dimY, secRight, dimY)
        AddLine(cutDims, tg, secRight, secTop, dimX + 0.2, secTop)
        AddLine(cutDims, tg, secRight, secBottom, dimX + 0.2, secBottom)
        AddArrowLine(cutDims, tg, dimX, secBottom, dimX, secTop)
    Finally
        cutDims.ExitEdit()
    End Try
    SchemeNote(cutNotes, tg, (secLeft + secRight) / 2 - 0.5, dimY + 0.65, FormatMm(section.Width / section.Scale * 10), 0.35)
    SchemeNote(cutNotes, tg, dimX + 0.3, (secTop + secBottom) / 2 + 0.25, FormatMm(section.Height / section.Scale * 10), 0.35)
    Dim labelY As Double = dimY - 1.0
    Try
        section.Label.Position = tg.CreatePoint2d((secLeft + secRight) / 2, labelY)
    Catch
    End Try
    drawing.Update()
    ' рамка рисунка: вся схема — земля, «Г», вид спереди, разрез, габариты и подпись
    Dim schemeLeft As Double = Math.Min(gl, gDimX - 1.3) - 0.4, schemeRight As Double = Math.Max(gr, dimX + 1.6) + 0.4
    Dim schemeTop As Double = fTop + 0.5, schemeBottom As Double = labelY - 0.8

    Dim drawingPath As String = System.IO.Path.Combine(
        folder, "Габаритные размеры" & If(drawing.IsInventorDWG, ".dwg", ".idw"))
    stage = "Сохранение чертежа: " & drawingPath
    drawing.SaveAs(drawingPath, False)

    stage = "Экспорт габаритного листа в PNG"
    drawing.Activate()
    sheet.Activate()
    drawing.SelectSet.Clear()
    Dim drawingView As Inventor.View = app.ActiveView
    drawingView.Fit()
    drawingView.Update()
    ' Камера — точно на блок видов с размерными линиями (+ поле 0,5 см), снимок — в тех же пропорциях:
    ' без пустых полей листа и окна, паспорт сам растягивает рисунок на страницу (2026-11-13).
    Dim boxLeft As Double = Math.Min(front.Left, top.Left) - 0.5
    Dim boxRight As Double = Math.Max(front.Left + front.Width, top.Left + top.Width) + dimRoom
    Dim boxTop As Double = front.Top + 0.5
    Dim boxBottom As Double = top.Top - top.Height - 0.5
    Dim boxW As Double = boxRight - boxLeft, boxH As Double = boxTop - boxBottom
    Dim cam As Inventor.Camera = drawingView.Camera
    cam.Target = tg.CreatePoint((boxLeft + boxRight) / 2, (boxTop + boxBottom) / 2, 0)
    cam.Eye = tg.CreatePoint((boxLeft + boxRight) / 2, (boxTop + boxBottom) / 2, 10)
    cam.UpVector = tg.CreateUnitVector(0, 1, 0)
    cam.SetExtents(boxW, boxH)
    cam.ApplyWithoutTransition()
    Dim imageHeight As Integer = Math.Max(200, CInt(2400.0 * boxH / boxW))
    cam.SaveAsBitmapWithOptions(System.IO.Path.Combine(folder, "02_Габаритные размеры.png"), 2400, imageHeight, TransparentPngOptions(app))
    stage = "Экспорт схемы установки в PNG"
    installationSheet.Activate()
    drawing.SelectSet.Clear()
    Dim schemeView As Inventor.View = app.ActiveView
    schemeView.Fit()
    Dim sBoxLeft As Double = schemeLeft, sBoxRight As Double = schemeRight
    Dim sBoxTop As Double = schemeTop, sBoxBottom As Double = schemeBottom
    Dim sCam As Inventor.Camera = schemeView.Camera
    sCam.Target = tg.CreatePoint((sBoxLeft + sBoxRight) / 2, (sBoxTop + sBoxBottom) / 2, 0)
    sCam.Eye = tg.CreatePoint((sBoxLeft + sBoxRight) / 2, (sBoxTop + sBoxBottom) / 2, 10)
    sCam.UpVector = tg.CreateUnitVector(0, 1, 0)
    sCam.SetExtents(sBoxRight - sBoxLeft, sBoxTop - sBoxBottom)
    sCam.ApplyWithoutTransition()
    sCam.SaveAsBitmapWithOptions(System.IO.Path.Combine(folder, "03_Схема установки.png"), 2400,
        Math.Max(200, CInt(2400.0 * (sBoxTop - sBoxBottom) / (sBoxRight - sBoxLeft))), TransparentPngOptions(app))

    stage = "Загрузка рисунков на сайт"
    If MessageBox.Show("Загрузить рисунки на сайт (общий вид, габариты, схема установки)?", "Картинки для паспорта",
                       MessageBoxButtons.YesNo, MessageBoxIcon.Question,
                       MessageBoxDefaultButton.Button2) = DialogResult.Yes Then
        stage = "Чтение массы модели"
        Dim massKg As Double = ModelMassKg(model)
        Dim productId As String = UploadPassportImages(model, folder, dimensions, depthMm, massKg, stage)
        If productId <> "" Then
            stage = "Открытие шаблона паспорта на сайте"
            Dim templateUrl As String = "https://kppdf-crm.ru/db/app/#docs?tab=templates&of=doctpl&open=" & productId
            System.Diagnostics.Process.Start(New System.Diagnostics.ProcessStartInfo(templateUrl) With {.UseShellExecute = True})
            Return
        End If
    End If
    stage = "Открытие папки в Проводнике"
    System.Diagnostics.Process.Start("explorer.exe", """" & folder & """")
End Sub

Sub ClearTemplateGraphics(sheet As Inventor.Sheet)
    ' Шаблон ГОСТ хранит дополнительные графы отдельно от рамки и штампа.
    For i As Integer = sheet.SketchedSymbols.Count To 1 Step -1
        sheet.SketchedSymbols.Item(i).Delete()
    Next
    For i As Integer = sheet.Sketches.Count To 1 Step -1
        sheet.Sketches.Item(i).Delete()
    Next
End Sub

Sub HideForExport(v As Inventor.ObjectVisibility,
                  restore As Global.System.Collections.Generic.List(Of Action))
    HideVisible(v.OriginWorkPlanes, Sub(onValue) v.OriginWorkPlanes = onValue, restore)
    HideVisible(v.OriginWorkAxes, Sub(onValue) v.OriginWorkAxes = onValue, restore)
    HideVisible(v.OriginWorkPoints, Sub(onValue) v.OriginWorkPoints = onValue, restore)
    HideVisible(v.UserWorkPlanes, Sub(onValue) v.UserWorkPlanes = onValue, restore)
    HideVisible(v.UserWorkAxes, Sub(onValue) v.UserWorkAxes = onValue, restore)
    HideVisible(v.UserWorkPoints, Sub(onValue) v.UserWorkPoints = onValue, restore)
    HideVisible(v.UCSWorkPlanes, Sub(onValue) v.UCSWorkPlanes = onValue, restore)
    HideVisible(v.UCSWorkAxes, Sub(onValue) v.UCSWorkAxes = onValue, restore)
    HideVisible(v.UCSWorkPoints, Sub(onValue) v.UCSWorkPoints = onValue, restore)
    HideVisible(v.UCSTriads, Sub(onValue) v.UCSTriads = onValue, restore)
    HideVisible(v.Sketches, Sub(onValue) v.Sketches = onValue, restore)
    HideVisible(v.Sketches3D, Sub(onValue) v.Sketches3D = onValue, restore)
    HideVisible(v.SketchDimensions, Sub(onValue) v.SketchDimensions = onValue, restore)
    HideVisible(v.ConstructionSurfaces, Sub(onValue) v.ConstructionSurfaces = onValue, restore)
    HideVisible(v.Annotations3D, Sub(onValue) v.Annotations3D = onValue, restore)
    HideVisible(v.ComponentAnnotations3D, Sub(onValue) v.ComponentAnnotations3D = onValue, restore)
End Sub

Sub HideVisible(visible As Boolean, setVisible As Action(Of Boolean),
                restore As Global.System.Collections.Generic.List(Of Action))
    If Not visible Then Return
    restore.Add(Sub() setVisible(True))
    setVisible(False)
End Sub

' Масса модели, кг (0,1). Не посчиталась (нет материала, модель не обновлена) — 0: масса на сайт не пишется.
Function ModelMassKg(model As Inventor.Document) As Double
    Try
        Dim assembly As Inventor.AssemblyDocument = TryCast(model, Inventor.AssemblyDocument)
        Dim mass As Double
        If assembly IsNot Nothing Then
            mass = assembly.ComponentDefinition.MassProperties.Mass
        Else
            mass = DirectCast(model, Inventor.PartDocument).ComponentDefinition.MassProperties.Mass
        End If
        Dim kg As Double = model.UnitsOfMeasure.ConvertUnits(mass, Inventor.UnitsTypeEnum.kDatabaseMassUnits, "kg")
        Return If(Double.IsNaN(kg) OrElse Double.IsInfinity(kg) OrElse kg < 0, 0, Math.Round(kg, 1, MidpointRounding.AwayFromZero))
    Catch
        Return 0
    End Try
End Function

Function UploadPassportImages(model As Inventor.Document, folder As String,
                              dimensions As Double(), depthMm As Double, massKg As Double, ByRef stage As String) As String
    Dim fileName As String = System.IO.Path.GetFileNameWithoutExtension(model.FullFileName)
    Dim proposal As String = System.Text.RegularExpressions.Regex.Match(fileName, "^\d+(?=\.)").Value
    If proposal = "" Then proposal = fileName
    Dim sku As String = Microsoft.VisualBasic.Interaction.InputBox(
        "Укажите точный артикул изделия на сайте.", "Загрузка рисунков", proposal).Trim()
    If sku = "" Then Return ""

    Dim key As String = Global.System.Environment.GetEnvironmentVariable(
        "DATACORE_API_KEY", Global.System.EnvironmentVariableTarget.User)
    If String.IsNullOrWhiteSpace(key) Then
        key = Global.System.Environment.GetEnvironmentVariable("DATACORE_API_KEY")
    End If
    If String.IsNullOrWhiteSpace(key) OrElse Not key.Trim().StartsWith("kppd_", StringComparison.Ordinal) Then
        Throw New InvalidOperationException("Задайте машинный ключ kppd_… в переменной DATACORE_API_KEY.")
    End If

    Using handler As New Global.System.Net.Http.HttpClientHandler()
        handler.AllowAutoRedirect = False
        Using client As New Global.System.Net.Http.HttpClient(handler)
            client.BaseAddress = New Global.System.Uri("https://kppdf-crm.ru/db/api/")
            client.Timeout = TimeSpan.FromSeconds(90)
            client.DefaultRequestHeaders.Authorization =
                New System.Net.Http.Headers.AuthenticationHeaderValue("Bearer", key.Trim())

            stage = "Поиск изделия по артикулу " & sku
            Dim productId As String = Nothing
            Dim productName As String = Nothing
            Dim page As Integer = 1
            Const pageSize As Integer = 100
            Do
                Dim result As Global.System.Text.Json.JsonElement = RequestJson(client, Global.System.Net.Http.HttpMethod.Get,
                    "showcase?search=" & Global.System.Uri.EscapeDataString(sku) & "&limit=" & pageSize & "&page=" & page)
                For Each item As Global.System.Text.Json.JsonElement In result.GetProperty("items").EnumerateArray()
                    If Not String.Equals(JsonString(item, "sku"), sku, StringComparison.OrdinalIgnoreCase) Then Continue For
                    If productId IsNot Nothing Then
                        Throw New InvalidOperationException("Найдено несколько изделий с этим артикулом.")
                    End If
                    productId = ApiId(item)
                    productName = JsonString(item, "name")
                Next
                If page * pageSize >= result.GetProperty("total").GetInt32() Then Exit Do
                page += 1
            Loop
            If productId Is Nothing Then Throw New InvalidOperationException("Изделие с точным артикулом не найдено.")
            If MessageBox.Show("Артикул: " & sku & vbCrLf & "Изделие: " & productName & vbCrLf & vbCrLf &
                               "Загрузить общий вид, габариты и схему установки?",
                               "Подтвердите изделие", MessageBoxButtons.YesNo, MessageBoxIcon.Question,
                               MessageBoxDefaultButton.Button2) <> DialogResult.Yes Then Return ""
            ' Значения в карточку — по отдельному согласию: на сайте их могли уже поправить вручную (пользователь 2026-11-13)
            Dim massText As String = If(massKg > 0, massKg.ToString("0.0", Global.System.Globalization.CultureInfo.GetCultureInfo("ru-RU")) & " кг", "не определена — не запишется")
            Dim writeSize As Boolean = MessageBox.Show(
                "Записать в карточку изделия на сайте:" & vbCrLf &
                "Габариты Д × Ш × В: " & FormatMm(dimensions(0)) & " × " & FormatMm(dimensions(1)) & " × " & FormatMm(dimensions(2)) & " мм" & vbCrLf &
                "Масса: " & massText & vbCrLf & vbCrLf &
                "«Нет» — на сайте останутся прежние значения.",
                "Габариты и масса", MessageBoxButtons.YesNo, MessageBoxIcon.Question,
                MessageBoxDefaultButton.Button1) = DialogResult.Yes
            Dim writeDepth As Boolean = MessageBox.Show(
                "Записать в карточку изделия глубину Г = " & FormatMm(depthMm) & " мм?" & vbCrLf & vbCrLf &
                "«Нет» — на сайте останется прежнее значение.",
                "Глубина Г", MessageBoxButtons.YesNo, MessageBoxIcon.Question,
                MessageBoxDefaultButton.Button1) = DialogResult.Yes

            Dim photosPath As String = "products/" & productId & "/photos"
            stage = "Проверка существующих рисунков"
            Dim previous As Global.System.Collections.Generic.Dictionary(Of String, String) = ReadPassportSlots(client, photosPath)
            If previous.Count > 0 Then
                Dim overviewCount As Integer = Global.System.Linq.Enumerable.Count(previous.Values, Function(kind) kind = "overview")
                Dim dimensionsCount As Integer = Global.System.Linq.Enumerable.Count(previous.Values, Function(kind) kind = "dimensions")
                Dim foundationCount As Integer = Global.System.Linq.Enumerable.Count(previous.Values, Function(kind) kind = "foundation")
                If MessageBox.Show("На сайте уже есть рисунки:" & vbCrLf &
                                   "Общий вид: " & overviewCount & vbCrLf &
                                   "Габаритные размеры: " & dimensionsCount & vbCrLf & "Схема установки опор: " & foundationCount & vbCrLf & "Заменить их?",
                                   "Подтвердите замену", MessageBoxButtons.YesNo, MessageBoxIcon.Warning,
                                   MessageBoxDefaultButton.Button2) <> DialogResult.Yes Then Return ""
            End If

            stage = "Загрузка PNG общего вида"
            Dim overviewId As String = UploadPng(client, System.IO.Path.Combine(folder, "01_Общий вид.png"))
            stage = "Загрузка PNG габаритных размеров"
            Dim dimensionsId As String = UploadPng(client, System.IO.Path.Combine(folder, "02_Габаритные размеры.png"))
            stage = "Загрузка PNG схемы установки"
            Dim foundationId As String = UploadPng(client, System.IO.Path.Combine(folder, "03_Схема установки.png"))
            stage = "Повторная проверка существующих рисунков"
            Dim current As Global.System.Collections.Generic.Dictionary(Of String, String) = ReadPassportSlots(client, photosPath)
            If current.Count <> previous.Count OrElse
               Global.System.Linq.Enumerable.Any(previous, Function(entry) Not current.ContainsKey(entry.Key) OrElse current(entry.Key) <> entry.Value) Then
                Throw New InvalidOperationException("Рисунки изделия изменились во время загрузки. Проверьте их на сайте.")
            End If

            Dim newLinks As New Global.System.Collections.Generic.List(Of String)
            Try
                stage = "Привязка общего вида"
                newLinks.Add(AttachPassportImage(client, photosPath, overviewId, "overview"))
                stage = "Привязка габаритных размеров"
                newLinks.Add(AttachPassportImage(client, photosPath, dimensionsId, "dimensions"))
                stage = "Привязка схемы установки опор"
                newLinks.Add(AttachPassportImage(client, photosPath, foundationId, "foundation"))
                Dim payload As New Global.System.Collections.Generic.Dictionary(Of String, Object)
                If writeSize Then
                    payload.Add("dimensions", New With {
                        .length = dimensions(0), .width = dimensions(1),
                        .height = dimensions(2), .unit = "мм"})
                    If massKg > 0 Then payload.Add("weightKg", massKg)
                End If
                If writeDepth Then payload.Add("foundationDepth", depthMm)
                If payload.Count > 0 Then
                    stage = "Запись в карточку изделия: " & If(writeSize, "габариты и масса", "") & If(writeSize AndAlso writeDepth, ", ", "") & If(writeDepth, "глубина Г", "")
                    Dim json As String = Global.System.Text.Json.JsonSerializer.Serialize(payload)
                    Using body As New Global.System.Net.Http.StringContent(json, System.Text.Encoding.UTF8, "application/json")
                        RequestJson(client, New Global.System.Net.Http.HttpMethod("PATCH"), "showcase/" & productId, body)
                    End Using
                End If
            Catch
                For Each linkId As String In newLinks
                    Try
                        RequestJson(client, Global.System.Net.Http.HttpMethod.Delete, photosPath & "/" & linkId)
                    Catch
                        MessageBox.Show("Не удалось отменить новую привязку. Проверьте рисунки изделия на сайте.")
                    End Try
                Next
                Throw
            End Try

            stage = "Отключение прежних рисунков. Все три новых рисунка уже привязаны"
            For Each linkId As String In previous.Keys
                RequestJson(client, Global.System.Net.Http.HttpMethod.Delete, photosPath & "/" & linkId)
            Next
            If Not writeDepth Then Return productId
            stage = "Проверка сохранённой глубины Г"
            Dim saved As Global.System.Text.Json.JsonElement = RequestJson(client, Global.System.Net.Http.HttpMethod.Get, "showcase/" & productId)
            Dim savedDefaults As Global.System.Text.Json.JsonElement
            Dim depth As Global.System.Text.Json.JsonElement
            Dim savedMm As Double
            If Not saved.TryGetProperty("passportDefaults", savedDefaults) OrElse
               savedDefaults.ValueKind <> Global.System.Text.Json.JsonValueKind.Object OrElse
               Not savedDefaults.TryGetProperty("foundationDepth", depth) OrElse
               depth.ValueKind <> Global.System.Text.Json.JsonValueKind.Number OrElse
               Not depth.TryGetDouble(savedMm) OrElse savedMm <> depthMm Then
                Throw New InvalidOperationException("Рисунки загружены, но сайт не подтвердил глубину Г = " & FormatMm(depthMm) & " мм.")
            End If
            Return productId
        End Using
    End Using
End Function

Function ReadPassportSlots(client As Global.System.Net.Http.HttpClient, path As String) As Global.System.Collections.Generic.Dictionary(Of String, String)
    Dim slots As New Global.System.Collections.Generic.Dictionary(Of String, String)(StringComparer.Ordinal)
    Dim result As Global.System.Text.Json.JsonElement = RequestJson(client, Global.System.Net.Http.HttpMethod.Get, path & "?purpose=passport")
    For Each item As Global.System.Text.Json.JsonElement In result.EnumerateArray()
        Dim kind As String = JsonString(item, "kind")
        If kind = "overview" OrElse kind = "dimensions" OrElse kind = "foundation" Then slots.Add(ApiId(item), kind)
    Next
    Return slots
End Function

Function UploadPng(client As Global.System.Net.Http.HttpClient, path As String) As String
    ' 502/503/504 (сайт занят: перезапуск после выкладки, режим «только чтение») — до 4 попыток с паузой 10 с (2026-11-13)
    For attempt As Integer = 1 To 4
        Using form As New Global.System.Net.Http.MultipartFormDataContent()
            Dim file As New Global.System.Net.Http.ByteArrayContent(System.IO.File.ReadAllBytes(path))
            file.Headers.ContentType = New System.Net.Http.Headers.MediaTypeHeaderValue("image/png")
            form.Add(file, "file", System.IO.Path.GetFileName(path))
            Try
                Return ApiId(RequestJson(client, Global.System.Net.Http.HttpMethod.Post, "photos/upload?purpose=passport", form))
            Catch ex As InvalidOperationException When attempt < 4 AndAlso IsBusy(ex)
                System.Threading.Thread.Sleep(10000)
            End Try
        End Using
    Next
    Throw New InvalidOperationException("Загрузка не удалась")
End Function

Function AttachPassportImage(client As Global.System.Net.Http.HttpClient, path As String, photoId As String, kind As String) As String
    Dim json As String = Global.System.Text.Json.JsonSerializer.Serialize(New With { .photoId = photoId, .purpose = "passport", .kind = kind })
    Using body As New Global.System.Net.Http.StringContent(json, System.Text.Encoding.UTF8, "application/json")
        Return ApiId(RequestJson(client, Global.System.Net.Http.HttpMethod.Post, path, body))
    End Using
End Function

' Сайт перезапускается после выкладки (502/503/504) — до 4 попыток с паузой 10 с. Повторяются только запросы без тела
' (чтение и удаление); запрос с телом повторяет вызывающий (UploadPng).
Function IsBusy(ex As InvalidOperationException) As Boolean
    Return ex.Message.Contains("HTTP 502") OrElse ex.Message.Contains("HTTP 503") OrElse ex.Message.Contains("HTTP 504")
End Function

Function RequestJson(client As Global.System.Net.Http.HttpClient, method As Global.System.Net.Http.HttpMethod, path As String,
                     Optional body As Global.System.Net.Http.HttpContent = Nothing) As Global.System.Text.Json.JsonElement
    If body IsNot Nothing Then Return SendJson(client, method, path, body)
    For attempt As Integer = 1 To 4
        Try
            Return SendJson(client, method, path, Nothing)
        Catch ex As InvalidOperationException When attempt < 4 AndAlso IsBusy(ex)
            System.Threading.Thread.Sleep(10000)
        End Try
    Next
    Throw New InvalidOperationException("Сайт не отвечает: " & method.Method & " " & path)
End Function

Function SendJson(client As Global.System.Net.Http.HttpClient, method As Global.System.Net.Http.HttpMethod, path As String,
                  body As Global.System.Net.Http.HttpContent) As Global.System.Text.Json.JsonElement
    Using request As New Global.System.Net.Http.HttpRequestMessage(method, path)
        request.Content = body
        Using response As Global.System.Net.Http.HttpResponseMessage = client.SendAsync(request).GetAwaiter().GetResult()
            If Not response.IsSuccessStatusCode Then
                ' текст ответа сайта — в сообщение (обрезан): по нему видно, почему отказ (например, «только чтение»)
                Dim reason As String = ""
                Try
                    reason = response.Content.ReadAsStringAsync().GetAwaiter().GetResult()
                    reason = System.Text.RegularExpressions.Regex.Replace(reason, "<[^>]+>", " ").Trim()
                    If reason.Length > 300 Then reason = reason.Substring(0, 300) & "…"
                Catch
                End Try
                Throw New InvalidOperationException("Сайт вернул HTTP " & CInt(response.StatusCode) & " для " & method.Method & " " & path &
                    If(reason <> "", vbCrLf & "Ответ сайта: " & reason, ""))
            End If
            If response.StatusCode = Global.System.Net.HttpStatusCode.NoContent Then Return Nothing
            Using json As Global.System.Text.Json.JsonDocument = Global.System.Text.Json.JsonDocument.Parse(response.Content.ReadAsStringAsync().GetAwaiter().GetResult())
                Return json.RootElement.Clone()
            End Using
        End Using
    End Using
End Function

Function JsonString(item As Global.System.Text.Json.JsonElement, name As String) As String
    Dim value As Global.System.Text.Json.JsonElement
    If item.TryGetProperty(name, value) AndAlso value.ValueKind = Global.System.Text.Json.JsonValueKind.String Then Return value.GetString()
    Return ""
End Function

Function ApiId(item As Global.System.Text.Json.JsonElement) As String
    Dim id As String = JsonString(item, "id")
    If id = "" Then id = JsonString(item, "_id")
    If Not System.Text.RegularExpressions.Regex.IsMatch(id, "\A[0-9a-fA-F]{24}\z") Then
        Throw New InvalidOperationException("Сайт не вернул корректный идентификатор.")
    End If
    Return id
End Function

Function AddDimensions(sheet As Inventor.Sheet, front As Inventor.DrawingView,
                       top As Inventor.DrawingView, tg As Inventor.TransientGeometry) As Double()
    ' Габариты — по всей модели, низ вида = низ изделия (заглубление показывает «Схема установки», размер «Г»)
    Dim frontLeft As Double = front.Left
    Dim frontRight As Double = frontLeft + front.Width
    Dim frontBottom As Double = front.Top - front.Height
    Dim ground As Double = frontBottom
    Dim topBottom As Double = top.Top - top.Height
    Dim lengthMm As Double = front.Width / front.Scale * 10
    Dim widthMm As Double = top.Height / top.Scale * 10
    Dim heightMm As Double = (front.Top - ground) / front.Scale * 10
    If heightMm <= 0 Then
        Throw New InvalidOperationException("Линия покрытия должна быть ниже верха изделия.")
    End If

    Dim lengthY As Double = frontBottom - 0.75
    Dim heightX As Double = frontRight + 0.85
    Dim widthX As Double = top.Left + top.Width + 0.85
    Dim sketch As Inventor.DrawingSketch = sheet.Sketches.Add()
    sketch.Edit()
    Try
        AddLine(sketch, tg, frontLeft, frontBottom, frontLeft, lengthY - 0.15)
        AddLine(sketch, tg, frontRight, frontBottom, frontRight, lengthY - 0.15)
        AddArrowLine(sketch, tg, frontLeft, lengthY, frontRight, lengthY)
        AddLine(sketch, tg, frontRight, ground, heightX + 0.15, ground)
        AddLine(sketch, tg, frontRight, front.Top, heightX + 0.15, front.Top)
        AddArrowLine(sketch, tg, heightX, ground, heightX, front.Top)
        AddLine(sketch, tg, top.Left + top.Width, topBottom, widthX + 0.15, topBottom)
        AddLine(sketch, tg, top.Left + top.Width, top.Top, widthX + 0.15, top.Top)
        AddArrowLine(sketch, tg, widthX, topBottom, widthX, top.Top)
    Finally
        sketch.ExitEdit()
    End Try

    Dim notes As Inventor.GeneralNotes = sheet.DrawingNotes.GeneralNotes
    AddLabel(notes, tg, (frontLeft + frontRight) / 2, lengthY + 0.4, "Д")
    AddLabel(notes, tg, heightX + 0.4, (ground + front.Top) / 2, "В")
    AddLabel(notes, tg, widthX + 0.4, (topBottom + top.Top) / 2, "Ш")
    ' Строку «Габаритные размеры (Д × Ш × В): …» на рисунке не пишем: её печатает паспорт из размеров изделия (2026-11-13)
    Return New Double() {RoundMm(lengthMm), RoundMm(widthMm), RoundMm(heightMm)}
End Function

' Надпись схемы установки: обычный текст, затем размер шрифта в см (StyleOverride); не принял — остаётся обычной
Sub SchemeNote(notes As Inventor.GeneralNotes, tg As Inventor.TransientGeometry, x As Double, y As Double, text As String, sizeCm As Double)
    Dim n As Inventor.GeneralNote = notes.AddFitted(tg.CreatePoint2d(x, y), text)
    Try
        n.FormattedText = "<StyleOverride FontSize='" & sizeCm.ToString(System.Globalization.CultureInfo.InvariantCulture) & "'>" & text & "</StyleOverride>"
    Catch
    End Try
End Sub

Sub AddLine(sketch As Inventor.DrawingSketch, tg As Inventor.TransientGeometry,
            x1 As Double, y1 As Double, x2 As Double, y2 As Double)
    sketch.SketchLines.AddByTwoPoints(tg.CreatePoint2d(x1, y1), tg.CreatePoint2d(x2, y2))
End Sub

Sub AddArrowLine(sketch As Inventor.DrawingSketch, tg As Inventor.TransientGeometry,
                 x1 As Double, y1 As Double, x2 As Double, y2 As Double)
    Dim span As Double = Math.Sqrt((x2 - x1) ^ 2 + (y2 - y1) ^ 2)
    If span <= 0 Then Return
    AddLine(sketch, tg, x1, y1, x2, y2)
    Dim head As Double = Math.Min(0.24, span / 3)
    Dim dx As Double = (x2 - x1) / span * head
    Dim dy As Double = (y2 - y1) / span * head
    AddLine(sketch, tg, x1, y1, x1 + dx - dy / 3, y1 + dy + dx / 3)
    AddLine(sketch, tg, x1, y1, x1 + dx + dy / 3, y1 + dy - dx / 3)
    AddLine(sketch, tg, x2, y2, x2 - dx - dy / 3, y2 - dy + dx / 3)
    AddLine(sketch, tg, x2, y2, x2 - dx + dy / 3, y2 - dy - dx / 3)
End Sub

Sub AddLabel(notes As Inventor.GeneralNotes, tg As Inventor.TransientGeometry,
             x As Double, y As Double, label As String)
    Dim point As Inventor.Point2d = tg.CreatePoint2d(x, y)
    Dim note As Inventor.GeneralNote = notes.AddFitted(point, label)
    Dim bounds As Inventor.Box2d = note.RangeBox
    Dim centerX As Double = (bounds.MinPoint.X + bounds.MaxPoint.X) / 2
    Dim centerY As Double = (bounds.MinPoint.Y + bounds.MaxPoint.Y) / 2
    Dim position As Inventor.Point2d = note.Position
    note.Position = tg.CreatePoint2d(position.X + x - centerX, position.Y + y - centerY)
End Sub

' Ближайший масштаб уменьшения по ГОСТ 2.302, не крупнее maxScale (доля «лист / модель», напр. 0,1 = 1:10)
Function GostScale(maxScale As Double) As Double
    Dim gost As Double() = {1, 2, 2.5, 4, 5, 10, 15, 20, 25, 40, 50, 75, 100, 200, 400, 500, 800, 1000}
    For Each n As Double In gost
        If 1 / n <= maxScale + 0.000001 Then Return 1 / n
    Next
    Return 1 / gost(gost.Length - 1)
End Function

' «1:10», «1:2,5»
Function ScaleText(scale As Double) As String
    Return "1:" & Math.Round(1 / scale, 1).ToString("0.#", System.Globalization.CultureInfo.GetCultureInfo("ru-RU"))
End Function

Function FormatMm(value As Double) As String
    Return RoundMm(value).ToString("0", System.Globalization.CultureInfo.GetCultureInfo("ru-RU"))
End Function

Function RoundMm(value As Double) As Double
    Return Math.Round(value, MidpointRounding.AwayFromZero)
End Function

Sub SavePng(app As Inventor.Application, camera As Inventor.Camera,
            folder As String, name As String, height As Integer)
    camera.SaveAsBitmapWithOptions(
        System.IO.Path.Combine(folder, name), 2400, height, TransparentPngOptions(app))
End Sub

Function TransparentPngOptions(app As Inventor.Application) As Inventor.NameValueMap
    Dim options As Inventor.NameValueMap = app.TransientObjects.CreateNameValueMap()
    options.Add("TransparentBackground", True)
    Return options
End Function

' Конец правила «Картинки для паспорта».
