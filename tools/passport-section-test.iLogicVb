' ТЕСТ (2026-11-13, вариант 2): «Схема установки» — лист книжный. Сверху вид спереди с линией земли (плоскость XZ модели)
' и размером «Г» от земли до низа изделия; снизу разрез А-А по линии земли — взгляд сверху на опоры, с габаритами.
' Запуск: откройте сохранённую сборку или деталь → iLogic → внешнее правило из этого файла.
' Создаёт НОВЫЙ чертёж (ничего не сохраняет) и в конце показывает журнал шагов. Сработает — переносим в «Картинки для паспорта».
Sub Main()
    Dim app As Inventor.Application = ThisApplication
    Dim model As Inventor.Document = app.ActiveDocument
    Dim log As New System.Text.StringBuilder()
    Dim stage As String = "Начало"
    Try
        If model Is Nothing OrElse (model.DocumentType <> Inventor.DocumentTypeEnum.kAssemblyDocumentObject AndAlso
                                    model.DocumentType <> Inventor.DocumentTypeEnum.kPartDocumentObject) Then
            MessageBox.Show("Откройте сборку или деталь.", "Тест схемы установки") : Return
        End If
        Dim tg As Inventor.TransientGeometry = app.TransientGeometry

        stage = "1. Новый чертёж, лист книжный"
        Dim template As String = app.FileManager.GetTemplateFile(Inventor.DocumentTypeEnum.kDrawingDocumentObject,
            Inventor.SystemOfMeasureEnum.kMetricSystemOfMeasure, Inventor.DraftingStandardEnum.kGOST_DraftingStandard)
        Dim drawing As Inventor.DrawingDocument = CType(app.Documents.Add(Inventor.DocumentTypeEnum.kDrawingDocumentObject, template, True), Inventor.DrawingDocument)
        Dim sheet As Inventor.Sheet = drawing.Sheets.Item(1)
        sheet.Size = Inventor.DrawingSheetSizeEnum.kA4DrawingSheetSize
        sheet.Orientation = Inventor.PageOrientationTypeEnum.kPortraitPageOrientation
        If sheet.TitleBlock IsNot Nothing Then sheet.TitleBlock.Delete()
        If sheet.Border IsNot Nothing Then sheet.Border.Delete()
        log.AppendLine(stage & ": ок, лист " & Math.Round(sheet.Width, 1) & " × " & Math.Round(sheet.Height, 1) & " см")

        stage = "2. Вид спереди сверху листа"
        Dim front As Inventor.DrawingView = sheet.DrawingViews.AddBaseView(model, tg.CreatePoint2d(sheet.Width * 0.5, sheet.Height * 0.7), 1,
            Inventor.ViewOrientationTypeEnum.kFrontViewOrientation, Inventor.DrawingViewStyleEnum.kHiddenLineRemovedDrawingViewStyle)
        drawing.Update()
        front.Scale = front.Scale * Math.Min(sheet.Width * 0.6 / front.Width, sheet.Height * 0.36 / front.Height)
        drawing.Update()
        front.Position = tg.CreatePoint2d(sheet.Width * 0.5, sheet.Height * 0.7)
        drawing.Update()
        Dim fLeft As Double = front.Left, fRight As Double = front.Left + front.Width
        Dim fTop As Double = front.Top, fBottom As Double = front.Top - front.Height
        log.AppendLine(stage & ": ок, масштаб " & Math.Round(front.Scale, 4) & ", " & Math.Round(front.Width, 1) & " × " & Math.Round(front.Height, 1) & " см")

        stage = "3. Линия земли = плоскость XZ"
        Dim groundY As Double = front.ModelToSheetSpace(tg.CreatePoint(0, 0, 0)).Y
        Dim depthMm As Double = Math.Round((groundY - fBottom) / front.Scale * 10)
        log.AppendLine(stage & ": Y = " & Math.Round(groundY, 2) & " см (вид: низ " & Math.Round(fBottom, 2) & ", верх " & Math.Round(fTop, 2) & "); Г = " & depthMm & " мм")
        If groundY <= fBottom Then log.AppendLine("   ВНИМАНИЕ: плоскость XZ на уровне низа или ниже — изделие не заглублено, Г = 0")

        stage = "4. Линия разреза по земле (на виде спереди)"
        Dim cut As Inventor.DrawingSketch = front.Sketches.Add()
        cut.Edit()
        Try
            cut.SketchLines.AddByTwoPoints(cut.SheetToSketchSpace(tg.CreatePoint2d(fLeft - 0.5, groundY)),
                                          cut.SheetToSketchSpace(tg.CreatePoint2d(fRight + 0.5, groundY)))
        Finally
            cut.ExitEdit()
        End Try
        log.AppendLine(stage & ": ок")

        stage = "5. Разрез А-А"
        ' направление взгляда задаёт место разреза при создании: ВЫШЕ линии — смотрит вниз, на землю
        Dim section As Inventor.SectionDrawingView = sheet.DrawingViews.AddSectionView(front, cut,
            tg.CreatePoint2d(sheet.Width * 0.5, fTop + 4), Inventor.DrawingViewStyleEnum.kHiddenLineRemovedDrawingViewStyle,
            Scale:=front.Scale, ShowLabel:=True, Name:="А")
        drawing.Update()
        ' пока масштаб общий и X общий — края разреза = крайние опоры на виде спереди
        Dim postsLeft As Double = section.Left, postsRight As Double = section.Left + section.Width
        log.AppendLine(stage & ": ок, опоры на виде спереди от " & Math.Round(postsLeft, 2) & " до " & Math.Round(postsRight, 2) & " см")

        stage = "6. Линия земли, штриховка, размер Г у левой опоры"
        Dim gl As Double = fLeft - 0.8, gr As Double = fRight + 0.8
        Dim dimX As Double = postsLeft - 0.9
        Dim sk As Inventor.DrawingSketch = sheet.Sketches.Add()
        sk.Edit()
        Try
            Line(sk, tg, gl, groundY, gr, groundY)
            ' штриховка земли под линией: короткие косые черты через 0,5 см
            Dim x As Double = gl
            While x < gr - 0.3
                Line(sk, tg, x, groundY, x + 0.3, groundY - 0.3)
                x += 0.5
            End While
            If depthMm > 0 Then
                Line(sk, tg, postsLeft, fBottom, dimX - 0.2, fBottom)       ' короткая выносная от низа опоры
                Arrow(sk, tg, dimX, fBottom, dimX, groundY)                  ' размерная линия Г
            End If
        Finally
            sk.ExitEdit()
        End Try
        Dim notes As Inventor.GeneralNotes = sheet.DrawingNotes.GeneralNotes
        If depthMm > 0 Then Note(notes, tg, dimX - 0.75, (fBottom + groundY) / 2 + 0.3, "Г", 0.5, log)
        log.AppendLine(stage & ": ок")

        stage = "7. Разрез крупнее, сразу под видом спереди"
        section.ScaleFromBase = False
        section.Scale = section.Scale * Math.Min(sheet.Width * 0.6 / section.Width, sheet.Height * 0.2 / section.Height)
        drawing.Update()
        Dim secY As Double = Math.Max(fBottom - 2.5 - section.Height / 2, section.Height / 2 + 3)
        section.Position = tg.CreatePoint2d(sheet.Width * 0.5, secY)
        drawing.Update()
        section.Label.FormattedText = "<DrawingViewName/>-<DrawingViewName/>"
        Dim onSheet As Boolean = section.Left >= 0 AndAlso section.Left + section.Width <= sheet.Width AndAlso section.Top <= sheet.Height AndAlso section.Top - section.Height >= 0
        log.AppendLine(stage & ": масштаб " & Math.Round(section.Scale, 4) & ", " & Math.Round(section.Width, 1) & " × " & Math.Round(section.Height, 1) & " см, " & If(onSheet, "НА ЛИСТЕ", "ЗА ЛИСТОМ"))

        stage = "8. Габариты по разрезу, подпись А-А под ними"
        Dim l As Double = section.Left, r As Double = section.Left + section.Width
        Dim tp As Double = section.Top, bt As Double = section.Top - section.Height
        Dim dy As Double = bt - 0.9, dx As Double = r + 0.9
        Dim dims As Inventor.DrawingSketch = sheet.Sketches.Add()
        dims.Edit()
        Try
            Line(dims, tg, l, bt, l, dy - 0.2) : Line(dims, tg, r, bt, r, dy - 0.2) : Arrow(dims, tg, l, dy, r, dy)
            Line(dims, tg, r, tp, dx + 0.2, tp) : Line(dims, tg, r, bt, dx + 0.2, bt) : Arrow(dims, tg, dx, bt, dx, tp)
        Finally
            dims.ExitEdit()
        End Try
        Note(notes, tg, (l + r) / 2 - 0.5, dy + 0.65, Math.Round(section.Width / section.Scale * 10).ToString(), 0.35, log)
        Note(notes, tg, dx + 0.3, (tp + bt) / 2 + 0.25, Math.Round(section.Height / section.Scale * 10).ToString(), 0.35, log)
        Try
            section.Label.Position = tg.CreatePoint2d((l + r) / 2, dy - 1.0)
        Catch exL As Exception
            log.AppendLine("   подпись не сдвинулась: " & exL.Message)
        End Try
        drawing.Update()
        log.AppendLine(stage & ": ок, " & Math.Round(section.Width / section.Scale * 10) & " × " & Math.Round(section.Height / section.Scale * 10) & " мм")

        sheet.Activate()
        app.ActiveView.Fit()
        MessageBox.Show("ГОТОВО" & vbCrLf & vbCrLf & log.ToString() & vbCrLf & "В паспорт: «Глубина Г = " & depthMm & " мм»", "Тест схемы установки")
    Catch ex As Exception
        MessageBox.Show("ОШИБКА на шаге: " & stage & vbCrLf & ex.Message & vbCrLf & vbCrLf & "Журнал:" & vbCrLf & log.ToString(), "Тест схемы установки")
    End Try
End Sub

' Надпись: сначала заданным размером шрифта (см), не вышло — обычной надписью; причина — в журнал
Sub Note(notes As Inventor.GeneralNotes, tg As Inventor.TransientGeometry, x As Double, y As Double, text As String, sizeCm As Double, log As System.Text.StringBuilder)
    Dim n As Inventor.GeneralNote = notes.AddFitted(tg.CreatePoint2d(x, y), text)
    Try
        n.FormattedText = "<StyleOverride FontSize='" & sizeCm.ToString(System.Globalization.CultureInfo.InvariantCulture) & "'>" & text & "</StyleOverride>"
    Catch ex As Exception
        log.AppendLine("   надпись «" & text & "» — обычным шрифтом: " & ex.Message)
    End Try
End Sub

Sub Line(sk As Inventor.DrawingSketch, tg As Inventor.TransientGeometry, x1 As Double, y1 As Double, x2 As Double, y2 As Double)
    sk.SketchLines.AddByTwoPoints(tg.CreatePoint2d(x1, y1), tg.CreatePoint2d(x2, y2))
End Sub

' размерная линия со стрелками на концах (как AddArrowLine в «Картинках для паспорта»)
Sub Arrow(sk As Inventor.DrawingSketch, tg As Inventor.TransientGeometry, x1 As Double, y1 As Double, x2 As Double, y2 As Double)
    Dim span As Double = Math.Sqrt((x2 - x1) ^ 2 + (y2 - y1) ^ 2)
    If span <= 0 Then Return
    Line(sk, tg, x1, y1, x2, y2)
    Dim hd As Double = Math.Min(0.24, span / 3)
    Dim ux As Double = (x2 - x1) / span, uy As Double = (y2 - y1) / span
    Dim w As Double = hd * 0.35
    ' стрелка у начала
    Line(sk, tg, x1, y1, x1 + ux * hd - uy * w, y1 + uy * hd + ux * w)
    Line(sk, tg, x1, y1, x1 + ux * hd + uy * w, y1 + uy * hd - ux * w)
    ' стрелка у конца
    Line(sk, tg, x2, y2, x2 - ux * hd - uy * w, y2 - uy * hd + ux * w)
    Line(sk, tg, x2, y2, x2 - ux * hd + uy * w, y2 - uy * hd - ux * w)
End Sub
